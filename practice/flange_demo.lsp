;;; Practice script for Windows AutoCAD 2026: stepped flange plate (mm).
;;; Codex drives CADOUTLINE, CADHOLES, CADDIMS in order through native SCR.
;;; Loading only defines functions; the runner verifies each completed stage.
;;; Start in a NEW EMPTY drawing. Existing objects are never erased.
;;; Edit the parameters below, then reload in a new drawing to regenerate.
;;; WCS origin is the bounding-box lower-left; outline misses (0,0).
;;; The runner saves to a NEW name; these three drawing commands never save.

(setq fd:w 220.0 fd:h 160.0 fd:corner 8.0
      fd:step-x1 25.0 fd:step-x2 55.0 fd:step-y1 20.0 fd:step-y2 50.0
      fd:bore-d 60.0 fd:pcd 90.0 fd:bolt-d 10.0 fd:bolt-count 6
      fd:mount-d 9.0 fd:mount-x 45.0 fd:mount-y 40.0
      fd:slot-x 25.0 fd:slot-l 30.0 fd:slot-w 12.0)

(defun fd:p3 (p) (list (car p) (cadr p) 0.0))
(defun fd:add (a b) (mapcar '+ a b))
(defun fd:sub (a b) (mapcar '- a b))
(defun fd:mul (v k) (mapcar '(lambda (x) (* x k)) v))
(defun fd:unit (v / d) (setq d (distance '(0.0 0.0) v)) (fd:mul v (/ 1.0 d)))
(defun fd:centre () (list (/ fd:w 2.0) (/ fd:h 2.0)))
(defun fd:polar (p a r) (list (+ (car p) (* r (cos a))) (+ (cadr p) (* r (sin a)))))

(defun fd:make (data)
  (if (entmake data) (entlast) (progn (prompt "\nEntity creation failed.") (exit))))
(defun fd:layer (name colour weight ltype)
  (if (not (tblsearch "LAYER" name))
    (entmake (list '(0 . "LAYER") '(100 . "AcDbSymbolTableRecord")
      '(100 . "AcDbLayerTableRecord") (cons 2 name) '(70 . 0)
      (cons 62 colour) (cons 6 ltype) (cons 370 weight)))))
(defun fd:setup (/ centre-file)
  (if (not (tblsearch "LTYPE" "CENTER"))
    (progn
      (setq centre-file (findfile "acadiso.lin"))
      (if (not centre-file) (setq centre-file (findfile "acad.lin")))
      (if centre-file
        (command-s "_.-LINETYPE" "_Load" "CENTER" centre-file "")
        (progn (prompt "\nCentre linetype file not found; no geometry created.") (exit)))))
  (fd:layer "OUTLINE" 7 50 "Continuous")
  (fd:layer "HOLE" 7 50 "Continuous")
  (fd:layer "CENTER" 8 18 "CENTER")
  (fd:layer "DIM" 3 18 "Continuous")
  (fd:layer "TEXT" 7 18 "Continuous")
  (if (not (tblsearch "STYLE" "CODEX_TEXT"))
    (entmake '((0 . "STYLE") (100 . "AcDbSymbolTableRecord")
      (100 . "AcDbTextStyleTableRecord") (2 . "CODEX_TEXT") (70 . 0)
      (40 . 0.0) (41 . 1.0) (50 . 0.0) (71 . 0)
      (42 . 3.5) (3 . "seguisym.ttf") (4 . ""))))
  (setvar "INSUNITS" 4)
  (setvar "LUNITS" 2)
  (setvar "LUPREC" 3)
  (setvar "LTSCALE" 1.0)
  (setvar "CELTSCALE" 1.0))

(defun fd:exists (layer)
  (ssget "_X" (list (cons 8 layer) '(410 . "Model"))))
(defun fd:poly (vertices layer / data v)
  (setq data (list '(0 . "LWPOLYLINE") '(100 . "AcDbEntity")
    (cons 8 layer) '(100 . "AcDbPolyline") (cons 90 (length vertices))
    '(70 . 1) '(38 . 0.0)))
  (foreach v vertices
    (setq data (append data (list (cons 10 (car v)) (cons 42 (cadr v))))))
  (fd:make data))
(defun fd:circle (p r layer)
  (fd:make (list '(0 . "CIRCLE") '(100 . "AcDbEntity") (cons 8 layer)
    '(100 . "AcDbCircle") (cons 10 (fd:p3 p)) (cons 40 r))))
(defun fd:line (p q layer)
  (fd:make (list '(0 . "LINE") '(100 . "AcDbEntity") (cons 8 layer)
    '(100 . "AcDbLine") (cons 10 (fd:p3 p)) (cons 11 (fd:p3 q)))))
(defun fd:cross (p size)
  (fd:line (fd:add p (list (- size) 0.0)) (fd:add p (list size 0.0)) "CENTER")
  (fd:line (fd:add p (list 0.0 (- size))) (fd:add p (list 0.0 size)) "CENTER"))
(defun fd:text (p height text)
  (fd:make (list '(0 . "TEXT") '(100 . "AcDbEntity") '(8 . "TEXT")
    '(100 . "AcDbText") (cons 10 (fd:p3 p)) (cons 40 height)
    (cons 1 text) '(7 . "CODEX_TEXT") '(50 . 0.0))))

(defun fd:corners ()
  (list (list 0.0 fd:step-y2)
    (list fd:step-x1 fd:step-y2) (list fd:step-x1 fd:step-y1)
    (list fd:step-x2 fd:step-y1) (list fd:step-x2 0.0)
    (list (- fd:w fd:step-x2) 0.0)
    (list (- fd:w fd:step-x2) fd:step-y1)
    (list (- fd:w fd:step-x1) fd:step-y1)
    (list (- fd:w fd:step-x1) fd:step-y2) (list fd:w fd:step-y2)
    (list fd:w (- fd:h fd:step-y2))
    (list (- fd:w fd:step-x1) (- fd:h fd:step-y2))
    (list (- fd:w fd:step-x1) (- fd:h fd:step-y1))
    (list (- fd:w fd:step-x2) (- fd:h fd:step-y1))
    (list (- fd:w fd:step-x2) fd:h) (list fd:step-x2 fd:h)
    (list fd:step-x2 (- fd:h fd:step-y1))
    (list fd:step-x1 (- fd:h fd:step-y1))
    (list fd:step-x1 (- fd:h fd:step-y2))
    (list 0.0 (- fd:h fd:step-y2))))
(defun fd:rounded (points r / i n p a b u v turn vertices bulge)
  (setq i 0 n (length points) vertices nil)
  (repeat n
    (setq p (nth i points) a (nth (rem (+ i n -1) n) points)
      b (nth (rem (+ i 1) n) points)
      u (fd:unit (fd:sub p a)) v (fd:unit (fd:sub b p))
      turn (- (* (car u) (cadr v)) (* (cadr u) (car v)))
      bulge (* turn (/ (sin (/ pi 8.0)) (cos (/ pi 8.0)))))
    (setq vertices (append vertices
      (list (list (fd:sub p (fd:mul u r)) bulge)
            (list (fd:add p (fd:mul v r)) 0.0))))
    (setq i (1+ i)))
  vertices)
(defun fd:outline ()
  (if (fd:exists "OUTLINE")
    (prompt "\nOUTLINE already contains objects; use a new empty drawing to regenerate.")
    (progn
      (fd:poly (fd:rounded (fd:corners) fd:corner) "OUTLINE")
      (prompt (strcat "\nStage 1: closed outline with "
        (itoa (length (fd:corners))) " fillets R" (rtos fd:corner 2 3)
        " completed.")))))

(defun fd:slot (p / a r x y)
  (setq a (/ (- fd:slot-l fd:slot-w) 2.0) r (/ fd:slot-w 2.0)
    x (car p) y (cadr p))
  (fd:poly (list
    (list (list (- x a) (- y r)) 0.0)
    (list (list (+ x a) (- y r)) 1.0)
    (list (list (+ x a) (+ y r)) 0.0)
    (list (list (- x a) (+ y r)) 1.0)) "HOLE")
  (fd:cross p (+ (/ fd:slot-l 2.0) 3.0)))
(defun fd:mounts ()
  (list (list fd:mount-x fd:mount-y)
    (list (- fd:w fd:mount-x) fd:mount-y)
    (list fd:mount-x (- fd:h fd:mount-y))
    (list (- fd:w fd:mount-x) (- fd:h fd:mount-y))))
(defun fd:holes (/ c i a p)
  (cond
    ((not (fd:exists "OUTLINE")) (prompt "\nRun CADOUTLINE first."))
    ((fd:exists "HOLE") (prompt "\nHOLE already contains objects; stage not repeated."))
    (T
      (setq c (fd:centre))
      (fd:circle c (/ fd:bore-d 2.0) "HOLE")
      (fd:circle c (/ fd:pcd 2.0) "CENTER")
      (fd:line (list -5.0 (cadr c)) (list (+ fd:w 5.0) (cadr c)) "CENTER")
      (fd:line (list (car c) -5.0) (list (car c) (+ fd:h 5.0)) "CENTER")
      (setq i 0)
      (repeat fd:bolt-count
        (setq a (* 2.0 pi (/ i (float fd:bolt-count)))
          p (fd:polar c a (/ fd:pcd 2.0)))
        (fd:circle p (/ fd:bolt-d 2.0) "HOLE")
        (fd:cross p (+ (/ fd:bolt-d 2.0) 2.0))
        (setq i (1+ i)))
      (foreach p (fd:mounts)
        (fd:circle p (/ fd:mount-d 2.0) "HOLE")
        (fd:cross p (+ (/ fd:mount-d 2.0) 2.0)))
      (fd:slot (list fd:slot-x (cadr c)))
      (fd:slot (list (- fd:w fd:slot-x) (cadr c)))
      (prompt (strcat "\nStage 2: "
        (itoa (+ 1 fd:bolt-count (length (fd:mounts))))
        " actual circular holes, 2 closed slots and centre lines completed."
        " The pitch circle is auxiliary.")))))

(defun fd:find-circle (p r layer / s i e d found)
  (setq s (ssget "_X" (list '(0 . "CIRCLE") (cons 8 layer) '(410 . "Model")))
    i 0 found nil)
  (if s
    (repeat (sslength s)
      (setq e (ssname s i) d (entget e))
      (if (and (equal (cdr (assoc 10 d)) (fd:p3 p) 0.000001)
               (equal (cdr (assoc 40 d)) r 0.000001))
        (setq found e))
      (setq i (1+ i))))
  found)
(defun fd:dim-style ()
  (setvar "DIMTXSTY" "CODEX_TEXT")
  (setvar "DIMTXT" 3.5) (setvar "DIMASZ" 2.5) (setvar "DIMSCALE" 1.0)
  (setvar "DIMLFAC" 1.0) (setvar "DIMRND" 0.0)
  (setvar "DIMALT" 0) (setvar "DIMPOST" "")
  (setvar "DIMEXO" 1.2) (setvar "DIMEXE" 1.8) (setvar "DIMGAP" 1.0)
  (setvar "DIMDEC" 0) (setvar "DIMZIN" 8) (setvar "DIMTAD" 1)
  (setvar "DIMTIH" 0) (setvar "DIMTOH" 0) (setvar "DIMTMOVE" 1)
  (setvar "DIMCEN" 0.0) (setvar "DIMCLRD" 256)
  (setvar "DIMCLRE" 256) (setvar "DIMCLRT" 256)
  (setvar "DIMASSOC" 1)
  (if (not (tblsearch "DIMSTYLE" "CODEX_MM"))
    (command-s "_.-DIMSTYLE" "_Save" "CODEX_MM"))
  (setvar "CLAYER" "DIM"))
(defun fd:dim-h (p q y)
  (command-s "_.DIMLINEAR" (fd:p3 p) (fd:p3 q) "_Horizontal"
    (list (/ (+ (car p) (car q)) 2.0) y 0.0)))
(defun fd:dim-v (p q x)
  (command-s "_.DIMLINEAR" (fd:p3 p) (fd:p3 q) "_Vertical"
    (list x (/ (+ (cadr p) (cadr q)) 2.0) 0.0)))
(defun fd:dim-dia (p radius layer location text / e)
  (setq e (fd:find-circle p radius layer))
  (if e
    (if text
      (command-s "_.DIMDIAMETER" (list e (fd:p3 (fd:polar p (angle p location) radius))) "_Text" text (fd:p3 location))
      (command-s "_.DIMDIAMETER" (list e (fd:p3 (fd:polar p (angle p location) radius))) (fd:p3 location)))))
(defun fd:dim-radius (centre edge textpoint)
  (fd:make (list '(0 . "DIMENSION") '(100 . "AcDbEntity") '(8 . "DIM")
    '(100 . "AcDbDimension") (cons 10 (fd:p3 centre))
    (cons 11 (fd:p3 textpoint)) '(70 . 164)
    '(1 . "R<>") '(3 . "CODEX_MM")
    '(100 . "AcDbRadialDimension") (cons 15 (fd:p3 edge)) '(40 . 20.0))))
(defun fd:dimensions (/ c xs ys i p)
  (cond
    ((not (fd:exists "HOLE")) (prompt "\nRun CADHOLES first."))
    ((fd:exists "DIM") (prompt "\nDIM already contains objects; stage not repeated."))
    (T
      (fd:dim-style) (setq c (fd:centre))
      (fd:dim-h (list 0.0 (cadr c)) (list fd:w (cadr c)) -50.0)
      (fd:dim-v (list (car c) 0.0) (list (car c) fd:h) (+ fd:w 50.0))
      ;; Theoretical sharp-corner step dimensions.
      (setq xs (list 0.0 fd:step-x1 fd:step-x2
        (- fd:w fd:step-x2) (- fd:w fd:step-x1) fd:w)
        ys (list (- fd:h fd:step-y2) (- fd:h fd:step-y1) fd:h
          fd:h (- fd:h fd:step-y1) (- fd:h fd:step-y2)) i 0)
      (repeat 5
        (fd:dim-h (list (nth i xs) (nth i ys))
          (list (nth (1+ i) xs) (nth (1+ i) ys)) (+ fd:h 23.0))
        (setq i (1+ i)))
      (setq ys (list 0.0 fd:step-y1 fd:step-y2
        (- fd:h fd:step-y2) (- fd:h fd:step-y1) fd:h)
        xs (list fd:step-x2 fd:step-x1 0.0 0.0 fd:step-x1 fd:step-x2) i 0)
      (repeat 5
        (fd:dim-v (list (nth i xs) (nth i ys))
          (list (nth (1+ i) xs) (nth (1+ i) ys)) -25.0)
        (setq i (1+ i)))
      ;; Mounting hole datum offsets and centre distances.
      (fd:dim-h (list 0.0 fd:step-y2) (list fd:mount-x fd:mount-y) -17.0)
      (fd:dim-h (list fd:mount-x fd:mount-y)
        (list (- fd:w fd:mount-x) fd:mount-y) -17.0)
      (fd:dim-v (list fd:step-x2 0.0) (list fd:mount-x fd:mount-y) -45.0)
      (fd:dim-v (list fd:mount-x fd:mount-y)
        (list fd:mount-x (- fd:h fd:mount-y)) -45.0)
      ;; Slot position, overall length and width; right slot is symmetric.
      (fd:dim-h (list 0.0 fd:step-y2) (list fd:slot-x (cadr c)) -33.0)
      (fd:dim-v (list fd:step-x2 0.0) (list fd:slot-x (cadr c)) -65.0)
      (fd:dim-h (list (- fd:slot-x (/ fd:slot-l 2.0)) (cadr c))
        (list (+ fd:slot-x (/ fd:slot-l 2.0)) (cadr c)) (+ (cadr c) 19.0))
      (fd:dim-v (list fd:slot-x (- (cadr c) (/ fd:slot-w 2.0)))
        (list fd:slot-x (+ (cadr c) (/ fd:slot-w 2.0))) (+ fd:slot-x 27.0))
      (fd:dim-dia c (/ fd:bore-d 2.0) "HOLE" (fd:add c '(-7.0 8.0)) nil)
      (fd:dim-dia c (/ fd:pcd 2.0) "CENTER"
        (list (+ fd:w 18.0) 33.4118100139) "PCD <>")
      (setq p (fd:polar c (/ pi 3.0) (/ fd:pcd 2.0)))
      (fd:dim-dia p (/ fd:bolt-d 2.0) "HOLE"
        (list (+ fd:w 18.0) 146.0) (strcat (itoa fd:bolt-count) "x<> EQ SP"))
      (fd:dim-dia (list (- fd:w fd:mount-x) (- fd:h fd:mount-y))
        (/ fd:mount-d 2.0) "HOLE" (list (+ fd:w 18.0) (- fd:h fd:mount-y))
        (strcat (itoa (length (fd:mounts))) "x<>"))
      (fd:dim-radius (list fd:corner (- fd:h fd:step-y2 fd:corner))
        (list (- fd:corner (/ fd:corner (sqrt 2.0)))
          (+ (- fd:h fd:step-y2 fd:corner) (/ fd:corner (sqrt 2.0))))
        (list -12.0 (+ (- fd:h fd:step-y2) 12.0)))
      (fd:text '(-25.0 209.0) 5.0 "CODEX + AUTOCAD / STEPPED FLANGE PLATE")
      (fd:text '(0.0 -68.0) 3.5 "2D TRAINING DRAWING   |   UNITS: mm   |   SCALE 1:1")
      (fd:text '(0.0 -77.0) 3.5 (strcat "2 SLOTS: R"
        (rtos (/ fd:slot-w 2.0) 2 3) " ENDS, SYMMETRIC ABOUT PLATE CENTRELINES"))
      (fd:text '(0.0 -86.0) 3.5 (strcat "ALL "
        (itoa (length (fd:corners))) " OUTLINE CORNERS: R" (rtos fd:corner 2 3)))
      (command-s "_.DIMREGEN")
      (prompt "\nStage 3: native dimension entities and drawing notes completed."))))

(defun fd:run (fn / *error* saved item)
  (setq saved (mapcar '(lambda (n) (cons n (getvar n)))
    '("CMDECHO" "OSMODE" "CLAYER" "DIMASSOC" "ELEVATION" "THICKNESS")))
  (defun *error* (msg)
    (foreach item saved (setvar (car item) (cdr item)))
    (prompt (strcat "\nDrawing stopped: " msg)) (princ))
  (setvar "CMDECHO" 0) (setvar "OSMODE" 0)
  (setvar "TILEMODE" 1)
  (command-s "_.UCS" "_World")
  (setvar "ELEVATION" 0.0) (setvar "THICKNESS" 0.0)
  (fd:setup)
  (apply fn nil)
  (command-s "_.ZOOM" "_Extents")
  (foreach item saved (setvar (car item) (cdr item)))
  (princ))
(defun c:CADOUTLINE () (fd:run 'fd:outline))
(defun c:CADHOLES () (fd:run 'fd:holes))
(defun c:CADDIMS () (fd:run 'fd:dimensions))
(princ "\nLoaded flange_demo.lsp. Native runner executes the three stages in a new empty drawing.")
(princ)
